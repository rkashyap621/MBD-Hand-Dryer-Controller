# HDCR_Requirements

## HDCR-REQ-001: Fan and Heater ON — Hand Present, Normal Temperature (Functional)
If hand_distance < 10 cm for more than 1 second AND temperature < 65°C, then fan_status = ON and heater_status = ON

## HDCR-REQ-002: Fan ON, Heater OFF — Hand Present, High Temperature (Functional)
If hand_distance < 10 cm for more than 1 second AND temperature >= 70°C, then fan_status = ON and heater_status = OFF

## HDCR-REQ-003: Fan and Heater OFF — Hand Removed (Functional)
If (fan_status == ON OR heater_status == ON) AND hand_distance > 15 cm for more than 3 seconds, then fan_status = OFF and heater_status = OFF

## HDCR-REQ-004: Fan OFF — Maximum Run Time Exceeded (Functional)
If fan_status == ON continuously for 60 seconds, then fan_status = OFF and heater_status = OFF

## HDCR-REQ-005: Heater OFF — Overtemperature During Operation (Functional)
If fan_status = ON AND heater_status = ON AND temperature >= 70°C, then heater_status = OFF

## HDCR-REQ-006: Heater ON — Temperature Recovery During Operation (Functional)
| If fan_status = ON AND heater_status = OFF AND temperature < 65°C, then heater_status = ON |
| --- |
